FepLeanSymmetricBooleanGenerativeModel-Schema DEFINITIONS AUTOMATIC TAGS ::= BEGIN

-- GNN Model Schema Definition
-- Model: FepLean Symmetric Boolean Generative Model
-- Bridge P1 spike: the fep_lean active_inference.lean
-- GenerativeModel instance `symmetricBoolModel trueBiasedPolicyPrior`
-- (two policies, two hidden states, two observations, one step)
-- projected deterministically to GNN v1 syntax.
-- Extraction record (file:line in the fep_lean checkout at the
-- commit recorded under Signature):
-- - D initialState = fairBoolLaw (1/2, 1/2)
--   [def active_inference.lean:719-722; use :745]
-- - B transition = fairBoolKernel, policy-indexed, all entries 1/2
--   [def active_inference.lean:725-728; use :746]
-- - A likelihood = fairBoolKernel, all entries 1/2
--   [def active_inference.lean:725-728; use :747]
-- - C preferences = fairBoolLaw (1/2, 1/2)
--   [def active_inference.lean:719-722; use :748]
-- - E policyPrior = trueBiasedPolicyPrior: E(false)=1/4, E(true)=3/4
--   [def active_inference.lean:731-734; parameter :743,:749]
-- - Timescale: one transition application [active_inference.lean:30-32]
-- - The Lean GenerativeModel carries no Action type, so no `u`
--   variable or action edges are emitted.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "FepLean Symmetric Boolean Generative Model",
    version "1.0",
    annotation "Bridge P1 spike: the fep_lean active_inference.lean GenerativeModel instance `symmetricBoolModel trueBiasedPolicyPrior` (two policies, two hidden states, two observations, one step) projected deterministically to GNN v1 syntax. Extraction record (file:line in the fep_lean checkout at the commit recorded under Signature): - D initialState = fairBoolLaw (1/2, 1/2)   [def active_inference.lean:719-722; use :745] - B transition = fairBoolKernel, policy-indexed, all entries 1/2   [def active_inference.lean:725-728; use :746] - A likelihood = fairBoolKernel, all entries 1/2   [def active_inference.lean:725-728; use :747] - C preferences = fairBoolLaw (1/2, 1/2)   [def active_inference.lean:719-722; use :748] - E policyPrior = trueBiasedPolicyPrior: E(false)=1/4, E(true)=3/4   [def active_inference.lean:731-734; parameter :743,:749] - Timescale: one transition application [active_inference.lean:30-32] - The Lean GenerativeModel carries no Action type, so no `u`   variable or action edges are emitted.",
    variables {
        {
            name "A",
            varType "likelihood_matrix",
            dataType "float"
            dimensions { 2, 2 }
        },
        {
            name "B",
            varType "transition_matrix",
            dataType "float"
            dimensions { 2, 2, 2 }
        },
        {
            name "C",
            varType "preference_vector",
            dataType "float"
            dimensions { 2 }
        }
    }
}

END -- FepLeanSymmetricBooleanGenerativeModel-Schema


-- MODEL_DATA: {"model_name":"FepLean Symmetric Boolean Generative Model","version":"1.0","annotation":"Bridge P1 spike: the fep_lean active_inference.lean\nGenerativeModel instance `symmetricBoolModel trueBiasedPolicyPrior`\n(two policies, two hidden states, two observations, one step)\nprojected deterministically to GNN v1 syntax.\nExtraction record (file:line in the fep_lean checkout at the\ncommit recorded under Signature):\n- D initialState = fairBoolLaw (1/2, 1/2)\n  [def active_inference.lean:719-722; use :745]\n- B transition = fairBoolKernel, policy-indexed, all entries 1/2\n  [def active_inference.lean:725-728; use :746]\n- A likelihood = fairBoolKernel, all entries 1/2\n  [def active_inference.lean:725-728; use :747]\n- C preferences = fairBoolLaw (1/2, 1/2)\n  [def active_inference.lean:719-722; use :748]\n- E policyPrior = trueBiasedPolicyPrior: E(false)=1/4, E(true)=3/4\n  [def active_inference.lean:731-734; parameter :743,:749]\n- Timescale: one transition application [active_inference.lean:30-32]\n- The Lean GenerativeModel carries no Action type, so no `u`\n  variable or action edges are emitted.","variables":[{"name":"A","var_type":"likelihood_matrix","data_type":"float","dimensions":[2,2],"description":"likelihood : FiniteKernel State Outcome"},{"name":"B","var_type":"transition_matrix","data_type":"float","dimensions":[2,2,2],"description":"transition : Policy -> FiniteKernel State State"},{"name":"C","var_type":"preference_vector","data_type":"float","dimensions":[2],"description":"preferences : FiniteLaw Outcome"},{"name":"D","var_type":"prior_vector","data_type":"float","dimensions":[2],"description":"initialState : FiniteLaw State"},{"name":"E","var_type":"policy","data_type":"float","dimensions":[2],"description":"policyPrior : FiniteLaw Policy"},{"name":"s","var_type":"hidden_state","data_type":"float","dimensions":[2,1],"description":"initialState distribution"},{"name":"s_prime","var_type":"hidden_state","data_type":"float","dimensions":[2,1],"description":"predictedState (one-step)"},{"name":"o","var_type":"observation","data_type":"float","dimensions":[2,1],"description":"predictedOutcome distribution"},{"name":"\u03c0","var_type":"policy","data_type":"float","dimensions":[2],"description":"policy prior / posterior over policies"},{"name":"F","var_type":"hidden_state","data_type":"float","dimensions":[1],"description":"variationalFreeEnergy readout"},{"name":"G","var_type":"policy","data_type":"float","dimensions":[1],"description":"expectedFreeEnergy readout"},{"name":"t","var_type":"hidden_state","data_type":"integer","dimensions":[1],"description":"discrete time step (one-step model)"}],"connections":[{"source_variables":["D"],"target_variables":["s"],"connection_type":"directed","weight":null,"description":null},{"source_variables":["s"],"target_variables":["B"],"connection_type":"undirected","weight":null,"description":null},{"source_variables":["B"],"target_variables":["s_prime"],"connection_type":"directed","weight":null,"description":null},{"source_variables":["s_prime"],"target_variables":["A"],"connection_type":"undirected","weight":null,"description":null},{"source_variables":["A"],"target_variables":["o"],"connection_type":"undirected","weight":null,"description":null},{"source_variables":["E"],"target_variables":["\u03c0"],"connection_type":"directed","weight":null,"description":null},{"source_variables":["\u03c0"],"target_variables":["B"],"connection_type":"undirected","weight":null,"description":null},{"source_variables":["C"],"target_variables":["G"],"connection_type":"directed","weight":null,"description":null},{"source_variables":["G"],"target_variables":["\u03c0"],"connection_type":"directed","weight":null,"description":null}],"parameters":[{"name":"A","value":[[0.5,0.5],[0.5,0.5]],"type_hint":null,"description":null},{"name":"B","value":[[[0.5,0.5],[0.5,0.5]],[[0.5,0.5],[0.5,0.5]]],"type_hint":null,"description":null},{"name":"C","value":[[0.5,0.5]],"type_hint":null,"description":null},{"name":"D","value":[[0.5,0.5]],"type_hint":null,"description":null},{"name":"E","value":[[0.25,0.75]],"type_hint":null,"description":null},{"name":"num_timesteps","value":1,"type_hint":null,"description":"one-step model"}],"equations":[],"time_specification":{"time_type":"Dynamic","discretization":null,"horizon":1,"step_size":null},"ontology_mappings":[{"variable_name":"A","ontology_term":"LikelihoodMatrix","description":null},{"variable_name":"B","ontology_term":"TransitionMatrix","description":null},{"variable_name":"C","ontology_term":"Preferences","description":null},{"variable_name":"D","ontology_term":"PriorOverHiddenStates","description":null},{"variable_name":"E","ontology_term":"Habit","description":null},{"variable_name":"F","ontology_term":"VariationalFreeEnergy","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"t","ontology_term":"Time","description":null}]}
