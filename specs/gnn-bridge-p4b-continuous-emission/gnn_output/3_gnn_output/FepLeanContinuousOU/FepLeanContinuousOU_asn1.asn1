FepLeanContinuousOULinear-GaussianModel-Schema DEFINITIONS AUTOMATIC TAGS ::= BEGIN

-- GNN Model Schema Definition
-- Model: FepLean Continuous OU Linear-Gaussian Model
-- Bridge P4b slice: the fep_lean scalar OU filter instance
-- (rate=1, center=0, diffusionVarianceRate=2, stepDuration=1,
-- observation noise variance=1) projected deterministically to
-- GNN v1 continuous linear-Gaussian syntax under contract v0.2
-- rounding. Extraction record (file:line in the fep_lean
-- checkout at the commit recorded under Signature):
-- - F one-step decay = exp(-rate*t) = exp(-1)
--   [scalar_gaussian_semigroup.lean:42-43]
-- - Q one-step transition covariance = rate^-1*(1 - exp(-2*rate*t))
--   = 1 - exp(-2) [linear_gaussian_semigroup.lean:1217-1233]
-- - H identity readout [gaussian_filter.lean:46-49]
-- - R observation noise variance = 1
--   [posterior_convergence.lean:38-40]
-- - prior_mean = 0, prior_cov = stationary variance = 1 (proved)
--   [smooth_reference_kernel.lean:66-68, 96-101]

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "FepLean Continuous OU Linear-Gaussian Model",
    version "1.0",
    annotation "Bridge P4b slice: the fep_lean scalar OU filter instance (rate=1, center=0, diffusionVarianceRate=2, stepDuration=1, observation noise variance=1) projected deterministically to GNN v1 continuous linear-Gaussian syntax under contract v0.2 rounding. Extraction record (file:line in the fep_lean checkout at the commit recorded under Signature): - F one-step decay = exp(-rate*t) = exp(-1)   [scalar_gaussian_semigroup.lean:42-43] - Q one-step transition covariance = rate^-1*(1 - exp(-2*rate*t))   = 1 - exp(-2) [linear_gaussian_semigroup.lean:1217-1233] - H identity readout [gaussian_filter.lean:46-49] - R observation noise variance = 1   [posterior_convergence.lean:38-40] - prior_mean = 0, prior_cov = stationary variance = 1 (proved)   [smooth_reference_kernel.lean:66-68, 96-101]",
    variables {
        {
            name "x",
            varType "hidden_state",
            dataType "float"
            dimensions { 1, 1 }
        },
        {
            name "y",
            varType "hidden_state",
            dataType "float"
            dimensions { 1, 1 }
        },
        {
            name "F",
            varType "hidden_state",
            dataType "float"
            dimensions { 1, 1 }
        }
    }
}

END -- FepLeanContinuousOULinear-GaussianModel-Schema


-- MODEL_DATA: {"model_name":"FepLean Continuous OU Linear-Gaussian Model","version":"1.0","annotation":"Bridge P4b slice: the fep_lean scalar OU filter instance\n(rate=1, center=0, diffusionVarianceRate=2, stepDuration=1,\nobservation noise variance=1) projected deterministically to\nGNN v1 continuous linear-Gaussian syntax under contract v0.2\nrounding. Extraction record (file:line in the fep_lean\ncheckout at the commit recorded under Signature):\n- F one-step decay = exp(-rate*t) = exp(-1)\n  [scalar_gaussian_semigroup.lean:42-43]\n- Q one-step transition covariance = rate^-1*(1 - exp(-2*rate*t))\n  = 1 - exp(-2) [linear_gaussian_semigroup.lean:1217-1233]\n- H identity readout [gaussian_filter.lean:46-49]\n- R observation noise variance = 1\n  [posterior_convergence.lean:38-40]\n- prior_mean = 0, prior_cov = stationary variance = 1 (proved)\n  [smooth_reference_kernel.lean:66-68, 96-101]","variables":[{"name":"x","var_type":"hidden_state","data_type":"float","dimensions":[1,1],"description":"latent scalar state"},{"name":"y","var_type":"hidden_state","data_type":"float","dimensions":[1,1],"description":"observation"},{"name":"F","var_type":"hidden_state","data_type":"float","dimensions":[1,1],"description":"one-step transition (drift decay)"},{"name":"Q","var_type":"hidden_state","data_type":"float","dimensions":[1,1],"description":"process noise covariance"},{"name":"H","var_type":"hidden_state","data_type":"float","dimensions":[1,1],"description":"observation matrix (identity readout)"},{"name":"R","var_type":"hidden_state","data_type":"float","dimensions":[1,1],"description":"observation noise covariance"},{"name":"prior_mean","var_type":"prior_vector","data_type":"float","dimensions":[1,1],"description":"x_1 mean"},{"name":"prior_cov","var_type":"prior_vector","data_type":"float","dimensions":[1,1],"description":"x_1 covariance"},{"name":"u","var_type":"action","data_type":"float","dimensions":[1,1],"description":"control input (passive: zero)"},{"name":"t","var_type":"hidden_state","data_type":"integer","dimensions":[1],"description":"discrete step index"}],"connections":[{"source_variables":["F"],"target_variables":["x"],"connection_type":"directed","weight":null,"description":null},{"source_variables":["Q"],"target_variables":["x"],"connection_type":"directed","weight":null,"description":null},{"source_variables":["x"],"target_variables":["H"],"connection_type":"undirected","weight":null,"description":null},{"source_variables":["H"],"target_variables":["y"],"connection_type":"directed","weight":null,"description":null},{"source_variables":["R"],"target_variables":["y"],"connection_type":"directed","weight":null,"description":null},{"source_variables":["prior_mean"],"target_variables":["x"],"connection_type":"directed","weight":null,"description":null},{"source_variables":["prior_cov"],"target_variables":["x"],"connection_type":"directed","weight":null,"description":null}],"parameters":[{"name":"F","value":[[[0.36787944117144233]]],"type_hint":null,"description":null},{"name":"Q","value":[[[0.8646647167633873]]],"type_hint":null,"description":null},{"name":"H","value":[[[1.0]]],"type_hint":null,"description":null},{"name":"R","value":[[[1.0]]],"type_hint":null,"description":null},{"name":"prior_mean","value":[[0.0]],"type_hint":null,"description":null},{"name":"prior_cov","value":[[[1.0]]],"type_hint":null,"description":null},{"name":"ou_rate","value":1,"type_hint":null,"description":"selectedDynamics.rate"},{"name":"ou_center","value":0,"type_hint":null,"description":"selectedDynamics.center"},{"name":"diffusion_variance_rate","value":2,"type_hint":null,"description":"selectedDynamics.diffusionVarianceRate"},{"name":"step_duration","value":1,"type_hint":null,"description":"selectedFilter.stepDuration"},{"name":"observation_noise_variance","value":1,"type_hint":null,"description":"selectedGaussianFamily.variance"},{"name":"num_timesteps","value":1,"type_hint":null,"description":null}],"equations":[],"time_specification":{"time_type":"Dynamic","discretization":null,"horizon":1,"step_size":null},"ontology_mappings":[{"variable_name":"F","ontology_term":"StateTransitionMatrix","description":null},{"variable_name":"H","ontology_term":"ObservationMatrix","description":null},{"variable_name":"Q","ontology_term":"ProcessNoiseCovariance","description":null},{"variable_name":"R","ontology_term":"ObservationNoiseCovariance","description":null},{"variable_name":"prior_mean","ontology_term":"PriorMean","description":null},{"variable_name":"prior_cov","ontology_term":"PriorCovariance","description":null},{"variable_name":"x","ontology_term":"ContinuousHiddenState","description":null},{"variable_name":"y","ontology_term":"ContinuousObservation","description":null},{"variable_name":"t","ontology_term":"Time","description":null}]}
